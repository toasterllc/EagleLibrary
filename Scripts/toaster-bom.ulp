// This is a modified version of the bom.ulp script, which combines parts based on their part number attribute ('PN').
// It removes all settings provided by the original bom.ulp script, and exclusively outputs as CSV.
//
// - Toaster 2023-6-10

if (!schematic)
{
  dlgMessageBox (usage + "<hr><b>ERROR: No schematic!</b><p>\nThis program can only work in the schematic editor.");
  exit (1);
}

char Separator = ';';
string SeparatorString;
sprintf(SeparatorString, "%c", Separator);

int     NumParts;
int     Index[];
numeric string Lines[];
numeric string PartName[];
string  PartNumber[];
int     PartOurStock[];

int FoundAttributes = 0;            // # of different attribute names found in schematic.
numeric string AttributesList[];    // Sorted list of all attributes found in the schematic.
numeric string PartAttributes[];    // Adjusted list of attributes per part.

enum { ExportTypeFull, ExportTypeFabNextPCB, ExportTypeCancel };
int ExportType = 0;

int IncludePart(UL_PART P) {
    if (ExportType == ExportTypeFull) return 1;
    
    P.attributes(A) {
        if (A.name=="AS-MOUNT-FAB" && strtol(A.value)) {
            return 1;
        }
    }
    return 0;
}

void CollectPartData ()
{
    int Found = 0;
    int i;
    string attr[];

    NumParts = 0;

    // First, collect the names of all available attributes.
    FoundAttributes = 0;
    schematic (SCH)
    {
        SCH.allparts (P) // 2014-08-07
        {
            if (P.device.package)
            {
                if (P.populate)
                {
                    P.attributes (A)
                    {
                        if (0 == FoundAttributes)
                        {
                            // First one
                            AttributesList[0] = A.name;
                            FoundAttributes = 1;
                        }
                        else
                        {
                            Found = 0;
                            for (i = 0; i < FoundAttributes; i ++)
                            {
                                if (A.name == AttributesList[i])
                                {
                                    // Found an already listed atrribute
                                    Found = 1;
                                    break;
                                }
                            }
                            if (0 == Found)
                            {
                                // Attribute not listed, add at the end.
                                AttributesList[FoundAttributes] = A.name;
                                FoundAttributes ++;
                            }
                        }
                    }
                }
            }
        }
    }
    sort (FoundAttributes, AttributesList);
    // Second, collect all data
    schematic (SCH)
    {
        SCH.allparts (P)
        {
            if (P.device.package)
            {
                if (P.populate)
                {
                    if (IncludePart(P))
                    {
                        PartName[NumParts] = P.name;
                        // Zero all strings
                        for (i = 0; i < FoundAttributes; i ++)
                            attr[i] = "";
                        P.attributes(A)
                        {
                            for (i = 0; i < FoundAttributes; i ++)
                                if (A.name == AttributesList[i])
                                {
                                    attr[i] = A.value;
                                    break;
                                }
                        
                                if (A.name == "PN")
                                {
                                    PartNumber[NumParts] = A.value;
                                }
                                
                                if (A.name == "AS-OUR-STOCK")
                                {
                                    PartOurStock[NumParts] = strtol(A.value);
                                }
                        }
                        PartAttributes[NumParts] = strjoin(attr, Separator);
                        NumParts ++;
                    }
                }
            }
        }
    }
    
    sort(NumParts, Index, PartNumber, PartName, PartOurStock, PartAttributes);
}

void GenerateList_Full (void)
{
    int NumLines = 0;
    string attr[], s;

    s = strjoin(AttributesList, '\t');

    Lines[NumLines ++] = "Quantity\tParts\t" + s;
    for (int n1 = 0, n2 = 0; ++ n2 <= NumParts; )
    {
        int i1 = Index [n1];
        strsplit (attr, PartAttributes[i1], Separator);
        s = strjoin(attr, '\t');
        if (n2 < NumParts)
        {
            int i2 = Index [n2]; // 2012-11-08
            if (PartNumber[i1]!="" && PartNumber[i2]!="" && PartNumber[i1]==PartNumber[i2])
                continue;
        }
        string Quantity;
        sprintf (Quantity, "%d", n2 - n1);
        Lines[NumLines] = Quantity + "\t";
        for (;;)
        {
            Lines[NumLines] += PartName[i1];
            if (++n1 < n2)
            {
                i1 = Index [n1];
                Lines[NumLines] += ", ";
            }
            else
                break;
        }
        Lines[NumLines] += "\t" + s;
        NumLines ++;
    }
    Lines[NumLines] = "";
}



void GenerateList_FabNextPCB (void)
{
    int NumLines = 0;
    string attr[], s;

    s = strjoin(AttributesList, '\t');

    Lines[NumLines ++] = "Manufacturer Part Number\tQty\tDesignator\tCustomer Supply\tCustomer Remark";
    for (int n1 = 0, n2 = 0; ++ n2 <= NumParts; )
    {
        int i1 = Index [n1];
        strsplit (attr, PartAttributes[i1], Separator);
        s = strjoin(attr, '\t');
        if (n2 < NumParts)
        {
            int i2 = Index [n2];
            if (PartNumber[i1]!="" && PartNumber[i2]!="" && PartNumber[i1]==PartNumber[i2]) {
                // Require AS-OUR-STOCK to match for all parts with the same part number
                if (PartOurStock[i1] != PartOurStock[i2]) {
                    dlgMessageBox("AS-OUR-STOCK mismatch between " + PartName[i1] + " and " + PartName[i2]);
                    exit(1);
                }
                continue;
            }
        }
        
        // Part number
        Lines[NumLines] = PartNumber[i1] + "\t";
        
        // Quantity
        string Quantity;
        sprintf (Quantity, "%d", n2 - n1);
        Lines[NumLines] += Quantity + "\t";
        
        // Part names
        for (;;) {
            Lines[NumLines] += PartName[i1];
            if (++n1 < n2)
            {
                i1 = Index [n1];
                Lines[NumLines] += ", ";
            }
            else
                break;
        }
        Lines[NumLines] += "\t";
        
        // Our stock?
        Lines[NumLines] += (PartOurStock[i1] ? "Y" : "") + "\t";
        NumLines ++;
    }
    Lines[NumLines] = "";
}



string MakeList (void)
{
  string List;
  int numHeaders;

  for (int l = 0; Lines[l]; l ++)
  {
    string a [];
    int n = strsplit (a, Lines[l], '\t');
    if (l == 0)
      numHeaders = n;
    else
      n = numHeaders; // for the hidden key!
    for (int i = 0; i < n; i ++)
      List += "\"" + a[i] + "\"" + SeparatorString;
    List += "\n";
  }
  return List;
}

void SaveList (void)
{
  string FileName;
  schematic(SCH) FileName = filesetext (SCH.name, ".csv");
  FileName = dlgFileSave ("Save Bill Of Material", FileName);
  if (FileName)
  {
    output (FileName, "wt")
    {
      printf ("%s", MakeList ());
    }
  }
}

ExportType = dlgMessageBox("Select export type\t\t\t\t", "Full", "Fab (NextPCB)", "Cancel");
if (ExportType == ExportTypeCancel) exit(0);

CollectPartData();
switch (ExportType) {
case ExportTypeFull:        GenerateList_Full(); break;
case ExportTypeFabNextPCB:  GenerateList_FabNextPCB(); break;
}
SaveList();
